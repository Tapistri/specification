Tapistri DEFINITIONS AUTOMATIC TAGS ::= BEGIN
    -- primatives

    -- milliseconds from unix epoch 1-1-1970 @ 00:00:00 UTC
    UTCTimestamp ::= INTEGER (0..18446744073709551615)

    SignatureAlgorithm ::= ENUMERATED {
        sFNDSA512draft,
        ...
    }

    DigestAlgorithm ::= ENUMERATED {
        dSHA256,
        ...
    }

    KeyExchangeAlgorithm ::= ENUMERATED {
        kxMLKEM768,
        ...
    }

    Signature ::= SEQUENCE {
        algorithm SignatureAlgorithm,
        signatureValue OCTET STRING
    }

    Digest ::= SEQUENCE {
        algorithm DigestAlgorithm,
        digestValue OCTET STRING
    }

    ValidityPeriod ::= SEQUENCE {
        notBefore UTCTimestamp,
        notAfter UTCTimestamp
    }

    SigningKey ::= SEQUENCE {
        publicKey OCTET STRING,
        publicKeyAlgorithm SignatureAlgorithm,
        publicKeyFingerprint Digest
    }

    -- records (certificate payloads)

    InstanceAttestationRecord ::= SEQUENCE {
        identityFingerprint Digest,
        instanceKeyFingerprint Digest,
        proxyKeyFingerprint Digest,
        proxyKeyValidityPeriod ValidityPeriod
    }

    HistoricalKeyRecord ::= SEQUENCE {
        publicKey SigningKey,
        serialNumber INTEGER, -- position of the key in the keychain, starting at 0 for the first key
        validityPeriod ValidityPeriod
    }

    HistoricalKeyRevocationRecord ::= SEQUENCE {
        revokedKeyFingerprint Digest,
        revokedKeySerialNumber INTEGER, -- position of the revoked key
        serialNumber INTEGER, -- position of the record in the keychain
        revocationTime UTCTimestamp
    }

    -- certificates (signed records)

    -- self-signed
    IdentityCertificate ::= SEQUENCE {
        tbsIdentity SigningKey,
        signature Signature
    }

    HistoricalKeyRevocationCertificate ::= SEQUENCE {
        tbsRevocation HistoricalKeyRevocationRecord,
        identitySignature Signature
    }

    HistoricalKeyCertificate ::= SEQUENCE {
        tbsHistoricalKey HistoricalKeyRecord,
        signature Signature
    }

    InstanceAttestationCertificate ::= SEQUENCE {
        tbsInstanceAttestation InstanceAttestationRecord,
        instanceSignature Signature,
        proxySignature Signature
    }

    -- keychains
    IdentityKeychainCertificate ::= SEQUENCE {
        -- this record is signed by the identity key, and establishes the keychain for a given identity
        tbskeychainIdentifer SEQUENCE {
            clientIdentity IdentityCertificate,
            homeserverIdentity IdentityCertificate,
            instanceIdentityFingerprint Digest,
            clientIdentityFingerprint Digest
        },
        clientIdentitySignature Signature,
        instanceSignature Signature,

        history SEQUENCE OF CHOICE {
            historicalKey HistoricalKeyCertificate,
            revocationRecord HistoricalKeyRevocationCertificate
        }
    }

END
